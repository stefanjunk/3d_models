# -*- coding: utf-8 -*-
"""FreeCAD macro: Boolean closed base/cutter meshes and write an STL.

Edit the paths and OPERATION, then run as a macro or with FreeCADCmd.
The cutter must already be watertight and overlap the base surface.
"""
import Mesh

BASE_STL = "/absolute/path/base.stl"
RELIEF_STL = "/absolute/path/relief-patch.stl"
OUTPUT_STL = "/absolute/path/base-with-relief.stl"
OPERATION = "difference"  # difference, union, intersection

base = Mesh.Mesh(BASE_STL)
relief = Mesh.Mesh(RELIEF_STL)

if OPERATION == "difference":
    result = base.difference(relief)
elif OPERATION == "union":
    result = base.union(relief)
elif OPERATION == "intersection":
    result = base.intersection(relief)
else:
    raise ValueError("Unsupported OPERATION: " + OPERATION)

result.removeDuplicatedPoints()
result.harmonizeNormals()
result.write(OUTPUT_STL)
print("Wrote", OUTPUT_STL, "facets:", result.CountFacets)
