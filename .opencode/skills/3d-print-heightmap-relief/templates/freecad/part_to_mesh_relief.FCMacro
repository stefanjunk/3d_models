# -*- coding: utf-8 -*-
"""FreeCAD macro: tessellate a STEP/B-rep base before a mesh relief Boolean."""
import Part
import MeshPart

INPUT_STEP = "/absolute/path/base.step"
OUTPUT_STL = "/absolute/path/base.stl"
LINEAR_DEFLECTION_MM = 0.08
ANGULAR_DEFLECTION_RAD = 0.12

shape = Part.Shape()
shape.read(INPUT_STEP)
if shape.isNull():
    raise RuntimeError("Could not read STEP shape: " + INPUT_STEP)

mesh = MeshPart.meshFromShape(
    Shape=shape,
    LinearDeflection=LINEAR_DEFLECTION_MM,
    AngularDeflection=ANGULAR_DEFLECTION_RAD,
    Relative=False,
)
mesh.write(OUTPUT_STL)
print("Wrote", OUTPUT_STL, "facets:", mesh.CountFacets)
